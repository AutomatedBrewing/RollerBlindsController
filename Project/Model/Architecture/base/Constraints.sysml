package L0_Constraints {
    private import ISQ::*;
    private import SI::*;
    private import Stakeholders::*;
    private import BaseArchitecture::*;
    private import SystemObjectives::*;

    comment
    /* Constraints limits the solution space. */

    /* Category templates (Layer 1), same two-layer pattern as L0_Requirements. */
    requirement def BusinessConstraint {
        subject controller : BaseArchitecture::ShutterController;
    }
    requirement def PhysicalConstraint {
        subject controller : BaseArchitecture::ShutterController;
    }
    requirement def EnvironmentalConstraint {
        subject controller : BaseArchitecture::ShutterController;
    }
    requirement def ElectricalConstraint {
        subject controller : BaseArchitecture::ShutterController;
    }
    requirement def ArchitecturalConstraint {
        subject controller : BaseArchitecture::ShutterController;
    }

    package Business {
        requirement <'CNST-B-01'> costEffective : BusinessConstraint {
            subject controller : BaseArchitecture::ShutterController;
            stakeholder manufacturer : Stakeholders::Manufacturer;

            doc
            /* The controller shall achieve manufacturing cost below 50 PLN per unit. */

            attribute manufacturingCost; // unit: PLN (Polish Zloty); no SI currency unit exists

            require constraint {
                manufacturingCost <= 50
            }

            frame manufacturer.costConcern {
                redefines cost = manufacturingCost;
            }
        }
    } // package Business

    package Physical {
        requirement <'CNST-P-01'> compactDimensions : PhysicalConstraint {
            subject controller : BaseArchitecture::ShutterController;
            stakeholder user : Stakeholders::User;

            doc
            /* The controllers dimentions shall not exceed 40x40x20mm. */

            attribute width subsets ISQ::length;
            attribute length subsets ISQ::length;
            attribute height subsets ISQ::length;

            require constraint {
                width <= 40 [SI::mm] and length <= 40 [SI::mm] and height <= 20 [SI::mm]
            }

            frame user.minimalSize {
                redefines width = width;
                redefines length = length;
                redefines height = height;
            }
        }
    } // package Physical

    package Environmental {
        requirement <'CNST-E-01'> operatingConditions : EnvironmentalConstraint {
            subject controller : BaseArchitecture::ShutterController;
            stakeholder manufacturer : Stakeholders::Manufacturer;
            doc
            /* The controller shall operate in typical residential environmental conditions. */

            attribute minEnviromentTemperature subsets ISQ::thermodynamicTemperature;
            attribute maxEnviromentTemperature subsets ISQ::thermodynamicTemperature;

            require constraint {
                minEnviromentTemperature >= 0 ['°C'] and maxEnviromentTemperature <= 40 ['°C']
            }

            frame manufacturer.operatingConditionsConcern {
                redefines minimalWorkingTemperature = minEnviromentTemperature;
                redefines maximumWorkingTemperature = maxEnviromentTemperature;
            }
        }
    } // package Environmental

    package Electrical {
        requirement <'CNST-EL-01'> supplyVoltage : ElectricalConstraint {
            subject controller : BaseArchitecture::ShutterController;
            stakeholder manufacturer : Stakeholders::Manufacturer;
            doc
            /* The controller shall operate from a 12 VDC ±10% supply. */

            attribute supplyVoltage = 12 [SI::V];

            require constraint {
                supplyVoltage >= 10 [SI::V] and supplyVoltage <= 14 [SI::V]
            }
        }

        requirement <'CNST-EL-02'> switchingLoad : ElectricalConstraint {
            subject controller : BaseArchitecture::ShutterController;
            stakeholder manufacturer : Stakeholders::Manufacturer;
            doc
            /* The controller shall support shutter motors with operating current up to 8 A at 230 VAC. */

            attribute switchingCurrent = 8 [SI::A];
            attribute switchingVoltage = 230 [SI::V];

            require constraint {
                switchingCurrent <= 8 [SI::A] and switchingVoltage <= 230 [SI::V]
            }
        }

        requirement <'CNST-EL-03'> motorIsolation : ElectricalConstraint {
            subject controller : BaseArchitecture::ShutterController;
            stakeholder manufacturer : Stakeholders::Manufacturer;
            doc
            /* The motor control circuitry shall be galvanically isolated from low-voltage control logic. */
        }

        requirement <'CNST-EL-04'> inputIsolation : ElectricalConstraint {
            subject controller : BaseArchitecture::ShutterController;
            stakeholder manufacturer : Stakeholders::Manufacturer;
            doc
            /* The controller shall provide galvanic isolation for all external input interfaces. */
        }
    } // package Electrical

    package Architectural {
        requirement <'CNST-A-01'> noPositionFeedback : ArchitecturalConstraint {
            subject controller : BaseArchitecture::ShutterController;
            stakeholder manufacturer : Stakeholders::Manufacturer;
            doc
            /* The controller shall operate without position feedback from the shutter. */
        }

        requirement <'CNST-A-02'> timeBasedOperation : ArchitecturalConstraint {
            subject controller : BaseArchitecture::ShutterController;
            stakeholder manufacturer : Stakeholders::Manufacturer;
            doc
            /* The controller shall operate using configurable time-based shutter positioning. */
        }
    } // package Architectural
} // package L0_Constraints
