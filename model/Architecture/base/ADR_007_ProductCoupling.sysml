/* Architecture Decision Record: ADR-007 — Logical-to-Product Coupling Strategy
 *
 * Documents the coupling strategy (SYSMOD Tool 11.7) applied when deriving the
 * Product Architecture (SM-PRD-21) from the Logical Architecture (SM-PRD-20),
 * mirroring the role ADR-004 played for the Functional→Logical / Logical→Base
 * coupling decisions. Required before Product Architecture modeling begins,
 * per KnowledgeSource/integration/crossmapping/product-architecture.md §5
 * step 1.
 *
 * arc42 section: ARC-09 Architecture Decisions.
 */
package ADR_007_ProductCoupling {
    private import LogicalArchitecture::*;
    private import BaseArchitecture::*;
    private import ADR_004_LogicalCoupling::*;
    private import ADR_006_ProductRealizationStrategy::*;
    // Top-20 fix #17 (finalReviewReport.md corrective pass): 'ArchDecisionMeta'
    // is now declared once in ADR_Common and imported here instead of being
    // re-declared locally -- see that file's header for rationale.
    private import ADR_Common::*;

    package ADR_007 {
        @ArchDecisionMeta {
            decisionId   = "ADR-007";
            title        = "Strong coupling for clean 1:1 Logical-to-Product realizations; loose coupling (allocation) wherever ADR-006's software modularization splits one Logical component across multiple Product components";
            status       = "accepted";
            context      = "Per product-architecture.md §1 Dependencies, each product part def MUST specialize (':>') its Logical counterpart OR be covered by an 'allocation def LogicalToProduct'. ADR-006 deliberately splits LogicalControlUnit, LogicalMotorDrive, and LogicalUserNotification each into more than one Product component (a hardware element plus one or more firmware modules, or several firmware modules), to satisfy the Logical Architecture review's mandatory re-evaluation of LogicalControlUnit's concentration. A uniform coupling rule (either 'always strong' or 'always loose') would either force an artificial, information-losing 1:1 relabeling of a genuine 1-to-many concretization, or discard the strong-coupling clarity available for the components that DO concretize cleanly 1:1.";
            decision     = "Apply coupling per-component, mirroring ADR-004's precedent exactly: (1) STRONG COUPLING (':>') for every Logical component with an unambiguous 1:1 Product realization: LogicalMovementSupervisor :> ProductComponents::MovementSupervisorSoftware (identical scope: timer-based stop supervision + elapsed-time counting, now in firmware); LogicalDiagnostics :> ProductComponents::DiagnosticsSoftware (identical scope, now in firmware). BaseArchitecture::PowerModule (which has NO Logical Architecture counterpart, per ADR-004) is strong-coupled directly from Base to Product: ProductComponents::PowerSupplyModule :> BaseArchitecture::PowerModule — this is the first architecture layer at which PowerModule reappears, confirming the anticipated ownership already flagged in LogicalArchitecture.sysml's boundary-port-delegation comment. (2) LOOSE COUPLING (allocation def LogicalToProduct, see ProductArchitecture/LogicalToProductAllocation.sysml) for every Logical component ADR-006 splits across more than one Product component: LogicalControlUnit → {ControlMCU (hardware host), CommandArbitrationSoftware, MovementControlSoftware, ConfigurationManagerSoftware, MemoryManagerSoftware}; LogicalMotorDrive → {ControlMCU (host), MotorDriveControlSoftware, MotorDriveRelayModule}; LogicalUserNotification → {ControlMCU (host), UserFeedbackSoftware, AudibleNotificationBuzzer (formerly UserNotificationIndicator, LED replaced by active buzzer per ADR-008)}; and, because ControlMCU is the single shared physical host for ALL seven firmware modules (including the two strong-coupled ones), LogicalMovementSupervisor and LogicalDiagnostics EACH ALSO receive an additional loose-coupling allocation entry to ControlMCU (hardware hosting is a many-to-one relationship that strong coupling cannot express — a part def can specialize at most one direct Logical supertype per coupling arrow, so the hosting relationship is modeled as allocation, layered on top of the firmware-level strong coupling). (3) LogicalLocalRequestInterface and LogicalRemoteRequestInterface are LOOSELY coupled (not strong-coupled, a deliberate departure from the Logical/Base pattern for these same two components under ADR-004): ADR-006 places the raw dry-contact isolation/debounce responsibility in a single shared hardware type (ProductComponents::RequestInterfaceCircuit, instantiated twice) while the actual ControlCommand INTERPRETATION (direction/mode inference from signal timing) is realized in CommandArbitrationSoftware, since that firmware module already inspects both channels for arbitration and is the natural place to decode them without duplicating interpretation logic per channel. This 1-to-2 split (hardware conditioning + shared interpretation firmware) requires allocation, not specialization, for both Logical components. (4) EnclosureAndConnectors (mechanical) has no Logical or Base Architecture counterpart at all — it is a genuinely new Product-layer element introduced to satisfy physical/mechanical constraints (L0_Constraints::Physical::compactDimensions, REQ-Q-01, REQ-Q-05, REQ-E-01) that have no structural representation at any earlier architecture layer; it is traced directly to those constraints/requirements in Traceability::Traceability rather than through a Logical intermediate, consistent with how Product Architecture is explicitly permitted to introduce new implementation elements.";
            consequences = "1. Traceability queries for 'which Product component realizes Logical component X' must consult BOTH the ':>' specialization graph and the LogicalToProduct allocation def — mirroring exactly the same dual-mechanism query already required at the Functional→Logical/Logical→Base boundary per ADR-004. 2. Any future change to ADR-006's software-module boundaries (e.g., merging MovementControlSoftware and MotorDriveControlSoftware) requires revisiting the corresponding allocation entries here, but does NOT affect the two strong-coupled components (MovementSupervisorSoftware, DiagnosticsSoftware) or PowerSupplyModule, which remain stable specialization anchors. 3. ControlMCU itself is allocated FROM five different Logical components (logicalControlUnit, logicalMotorDrive, logicalUserNotification, logicalMovementSupervisor, logicalDiagnostics) without itself specializing any single one of them — this is an intentional many-to-one hosting pattern, not an incomplete or ambiguous allocation, and mirrors the same shared-platform pattern common in embedded product architectures.";
            alternatives = "A. Strong-couple every Product component to a Logical component by first artificially re-splitting the Logical Architecture itself to match the Product-layer software boundaries: rejected — the Logical Architecture is a validated, reviewed baseline (Scenarios already traced against it); re-opening it purely to preserve a uniform coupling mechanism would violate the layering principle that concretization happens downward, not by retrofitting upper layers to match lower-layer implementation convenience. B. Loose-couple every Product component uniformly (no strong coupling at all): rejected for the same reason ADR-004 rejected the equivalent uniform-loose-coupling alternative at the Logical/Base boundary — it discards the clarity and change-propagation benefit strong coupling provides for the components that genuinely do concretize 1:1 (MovementSupervisorSoftware, DiagnosticsSoftware, PowerSupplyModule).";
            rationale    = "This decision applies the exact per-component coupling methodology ADR-004 already established one layer up (strong coupling wherever a clean 1:1 match exists, loose coupling/allocation everywhere a deliberate split or hosting relationship exists), extending the same reviewed, precedented approach to the Logical→Product boundary rather than inventing a new coupling policy at this layer.";
        }
    }
} // package ADR_007_ProductCoupling
