package ProblemStatement {
    comment
    /* The Problem Statement is a clear and concise statement of
     * an unwelcome situation that the system of interest should
     * resolve.
     */

    concern NeedOfWindowRollerShutterController {
        doc
        /* Users need a way to control window roller shutters in both
         * local and remote contexts.
         *
         * Currently, roller shutters are often controlled only manually,
         * which limits convenience and integration with modern home
         * automation systems.
         *
         * This creates a gap between user expectations for automated,
         * remote-controlled environments and the limited capability
         * of existing installations.
         *
         * The problem exists in residential and building automation
         * contexts, where users want to control shutters conveniently
         * without being physically present at each window.
         *
         * This matters because improved control increases comfort,
         * energy efficiency, and integration with smart home systems.
         */
    }
} // package ProblemStatement
