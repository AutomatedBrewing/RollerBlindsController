package ProblemStatement {
    concern NeedOfWindowRollerShutterController {
        doc
        /* How to build window roller shutter controller that is controlled
         * locally and remotely (using home-automation system).
         * The controller should support:
         * - both full movement and manual positioning
         * - be addaptive to different sizes of window roller shutters
         * - be simple in assembly and require zero maintanance
         * - shall not rely on position feedback from window roller shutter
         */
    }
} // package ProblemStatement
